# Classic theme must delete any set value for the editor text so that it is calculated dynamically when needed
import CivilCvCAD

editorPrefs = CivilCvCAD.ParamGet("User parameter:BaseApp/Preferences/Mod/Editor")
editorPrefs.RemInt("Text")

appPrefs = CivilCvCAD.ParamGet("User parameter:BaseApp/Preferences/MainWindow")
appPrefs.RemString("QtStyle")
